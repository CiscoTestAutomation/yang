module jon {
  namespace "urn:jon";
  prefix jon;

  revision 2023-03-29 {
    description
      "Initial revision";
  }

  leaf foo {
    type string;
  }

  container tracking {
    leaf enabled {
      type boolean;
    }
  }

  list address {
    key "first last";
    ordered-by user;
    leaf last {
      type string;
      description "Last name";
    }
    leaf first {
      type string;
      description "First name";
    }
    leaf street {
      type string;
      description "Street name";
    }
    leaf city {
      type string;
      description "City name";
    }
  }

  leaf-list store {
    ordered-by user;
    default "Target";
  }

  container location {
    choice city {
      case ontario {
        list ontario {
          key "name";
          leaf name {
            type string;
          }
        }
      }
      case alberta {
        list alberta {
          key "name";
          leaf name {
            type string;
          }
        }
      }
    }
  }

  container numbers {
    choice number {
      case one {
        leaf first {
          type string;
        }
      }
      case two {
        leaf second {
          type string;
        }
        leaf third {
          type string;
        }
      }
    }
  }
}
